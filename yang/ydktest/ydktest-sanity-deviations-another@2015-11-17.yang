module ydktest-sanity-deviations-another {
    namespace "http://cisco.com/ns/yang/ydktest-sanity-deviations-another";
    prefix "ydkut-deviations-another";
    import ydktest-sanity { prefix ydkut; }
    organization "Cisco Systems, Inc.";

    contact
      "Cisco Systems, Inc.
       Customer Service

       Postal: 170 West Tasman Drive
       San Jose, CA 95134

       Tel: +1 800 553-NETS

       E-mail: cs-yang@cisco.com";

    description
      "This module contains a set of deviations of Open Config BGP YANG
       set for Cisco IOS-XR.

       Copyright (c) 2015 by Cisco Systems, Inc.
       All rights reserved.";

    revision "2015-11-17" {
        description
            "Initial commit";
    }
    deviation /ydkut:runner/ydkut:ytypes/ydkut:built-in-t/ydkut:llstring {
      deviate add {
        max-elements 7;
        min-elements 0;
      }
    }
    // not supported container
    deviation /ydkut:runner/ydkut:not-supported-1/ydkut:not-supported-1-2 {
      deviate not-supported;
    }
    // not supported list
    deviation /ydkut:runner/ydkut:not-supported-2 {
      deviate not-supported;
    }
    // not supported leaf
    deviation /ydkut:runner/ydkut:not-supported-1/ydkut:not-supported-leaf {
      deviate not-supported;
    }
}
