module oc-pattern {

  /*** NAMESPACE / PREFIX DEFINITION ***/

  namespace "http://cisco.com/ns/yang/oc-pattern";


  prefix "oc";

  /*** LINKAGE (IMPORTS / INCLUDES) ***/


  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:


     Copyright (c) 2013-2014 by Cisco Systems, Inc.
     All rights reserved.";

  revision "2015-11-17" {
    description
      "Initial revision.";
  }

  list oc-A {

    key a;

    leaf a {
      description "blah";
      type leafref{
        path "/oc:oc-A/oc:B/oc:b";
      }
    }

    container B {
      leaf b{
        type string;
      }
    }

  }
}
