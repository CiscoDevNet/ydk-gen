module ydktest-sanity-types {

  namespace "http://cisco.com/ns/yang/ydktest-sanity-types";

  prefix "ydkut-types";
  import ydktest-sanity { prefix ydkut; }

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:


     Copyright (c) 2013-2014 by Cisco Systems, Inc.
     All rights reserved.";

  revision "2016-04-11" {
    description
      "Initial revision.";
  }

  identity ydktest-type {
    base ydkut:base-identity;
    description
      "This identity is used as a base for all YDK types.";
  }

  identity other {
    base ydktest-type;
  }

  identity another-one {
    base ydktest-type;
    reference
      "YDK type for testing";
  }

}
