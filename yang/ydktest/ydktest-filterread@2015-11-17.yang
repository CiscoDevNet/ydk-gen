//   +--rw a
//      +--rw a1  string
//      +--rw a2  string
//      +--rw a3  string
//      +--rw b
//      |  +--rw b1   string
//      |  +--rw b2   string
//      |  +--rw b3   string
//      |  +--rw c
//      |  +--rw d
//      |     +--rw d1  string
//      |     +--rw d1  string
//      |     +--rw d1  string
//      |     +--rw e
//      |           +--rw e1 string
//      |           +--rw e2 string
//      +--rw lst* [number]
//         +--rw number int32
//         +--value string

module ydktest-filterread {

  namespace "http://cisco.com/ns/yang/ydk-filter";

  prefix "ydkflt";

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains definitions
     for the following management objects:


     Copyright (c) 2013-2014 by Cisco Systems, Inc.
     All rights reserved.";

  revision "2015-11-17" {
    description
      "Initial revision.";
  }

  container a {
    leaf a1 {
      type string;
    }
    leaf a2 {
      type string;
    }
    leaf a3 {
      type string;
    }
    container b {
      leaf b1 {
        type string;
      }
      leaf b2 {
        type string;
      }
      leaf b3 {
        type string;
      }
      container c {
        presence "Enables c";
      }
      container d {
        leaf d1 {
          type string;
        }
        leaf d2 {
          type string;
        }
        leaf d3 {
          type string;
        }
        container e {
          leaf e1 {
            type string;
          }
          leaf e2 {
            type string;
          }
        }
      }
      container f {
        presence "Enables e";
        leaf f1 {
          type string;
        }
      }
    }
    list lst {
      key number;
      leaf number {
        type int32;
      }
      leaf value {
        type string;
      }
    }
  }
}
