module ietf-aug-base-2 {

  namespace "http://cisco.com/ns/yang/ietf-aug-base-2";

  prefix "ietf-aug-base-2";

  organization "Cisco Systems, Inc.";

  contact
    "Cisco Systems, Inc.
     Customer Service

     Postal: 170 West Tasman Drive
     San Jose, CA 95134

     Tel: +1 800 553-NETS

     E-mail: cs-yang@cisco.com";

  description
    "This module is the augmentation base model for ydktest package.

     Copyright (c) 2013-2014 by Cisco Systems, Inc.
     All rights reserved.";

  revision "2016-07-01" {
    description
      "Initial revision.";
  }

  container cpython {
    container tools {
        container buildbot {
            leaf build {
                type string;
            }
        }
        container gdb {
            leaf libpython {
                type string;
            }
        }
    }
  }
}
