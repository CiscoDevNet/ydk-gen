module ietf-aug-base-1 {

  namespace "http://cisco.com/ns/yang/ietf-aug-base-1";

  prefix "ietf-aug-base-1";

  organization "Cisco Systems, Inc.";

  contact
    "Cisco Systems, Inc.
     Customer Service

     Postal: 170 West Tasman Drive
     San Jose, CA 95134

     Tel: +1 800 553-NETS

     E-mail: cs-yang@cisco.com";

  description
    "This module is the augmentation base model for ydktest package.

     Copyright (c) 2013-2014 by Cisco Systems, Inc.
     All rights reserved.";

  revision "2016-07-01" {
    description
      "Initial revision.";
  }

  container cpython {
    container doc {
      container c-api {
        leaf abstract {
          type string;
        }
      }
      container disutils {
        leaf apiref {
          type string;
        }
      }
    }
    container lib {
      container asyncio {
        leaf base-events {
          type string;
        }
      }
      container collections {
        leaf abc {
          type string;
        }
      }
    }
  }
}
