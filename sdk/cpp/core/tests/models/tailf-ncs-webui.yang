module tailf-ncs-webui {

  namespace "http://tail-f.com/ns/ncs-webui";

  prefix "ncs-webui";

  import tailf-webui {
    prefix webui;
  }

  import tailf-common {
    prefix tailf;
  }

  import tailf-ncs {
    prefix ncs;
  }

  organization "Tail-f Systems";

  description
    "This data model augments the tailf-webui data model and adds
     NCS specific component types. This makes it possible to create
     schematics containing, for example, NCS devices and device groups";

  revision 2013-01-16 {
    description
      "Released as part of NCS-2.2.

       Initial revision.";
  }

  augment "/webui:webui/webui:schematics/webui:panels/webui:panel"+
          "/webui:components/webui:component/webui:properties"+
          "/webui:component-type" {
    case device {
      container device {
        leaf device {
          mandatory true;
          tailf:info "NCS Device";
          type leafref {
            path "/ncs:devices/ncs:device/ncs:name";
          }
        }
        leaf image {
          mandatory true;
          tailf:info "A device image";
          type leafref {
            path "/webui:webui/webui:schematics/webui:assets/webui:asset"+
                 "/webui:name";
          }
        }
      }
    }
    case device-group {
      container device-group {
        leaf device-group {
          mandatory true;
          tailf:info "NCS Device group";
          type leafref {
            path "/ncs:devices/ncs:device-group/ncs:name";
          }
        }
        leaf image {
          mandatory true;
          tailf:info "Device group image";
          type leafref {
            path "/webui:webui/webui:schematics/webui:assets/webui:asset"+
                 "/webui:name";
          }
        }
      }
    }
  }


  typedef static-map-coordinate {
    description "Normalized relative coordinate";

    type decimal64 {
      fraction-digits 6;
      range "0 .. 1";
    }
  }

  grouping static-map-coordinates {
    container coord {
      leaf x {
        type static-map-coordinate;
      }

      leaf y {
        type static-map-coordinate;
      }
    }
  }


  augment "/webui:webui/webui:data-stores/webui:user-profile" {

    container static-backdrop {

      list bitmaps {
        key name;

        leaf name {
          tailf:info "Bitmap name";
          type string;
        }

        leaf image {
          tailf:info "Bitmap image data";
          type binary;
        }

      }

      list backdrops {
        key name;

        leaf name {
          type string;
        }


        leaf bitmap {
          mandatory true;
          type leafref {
            path '../../bitmaps/name';
          }
        }

        list devices {
          key name;

          leaf name {
            tailf:non-strict-leafref {
              path '/ncs:devices/ncs:device/ncs:name';
            }

            type string;
          }

          uses static-map-coordinates;
        }

      }

    }

  }

  augment "/webui:webui" {

    container icons {
      tailf:info "Webui icon information";

      list icon {
        key name;

        leaf name {
          type string;
        }


        leaf image {
          tailf:info "Image data";
          type binary;
        }
      }

      list device {
        tailf:info "Webui explicit device icons";

        key "name state size";

        leaf name {
          tailf:info "Device name";

          tailf:non-strict-leafref {
            path '/ncs:devices/ncs:device/ncs:name';
          }

          type string;
        }

        leaf state {
          tailf:info "Device UI state";

          type enumeration {
            enum error;
            enum disabled;
            enum enabled;
          }
        }

        leaf size {
          tailf:info "Icon size";

          type enumeration {
            enum small;
            enum medium;
            enum large;
          }
        }


        leaf icon {
          tailf:info "Device icon name";

          type leafref {
            path '../../icon/name';
          }
        }
      }

    }

  }

}
