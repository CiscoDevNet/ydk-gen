module tailf-ncs-ned {

  namespace "http://tail-f.com/ns/ncs-ned";
  prefix ned;

  organization "Tail-f Systems";

  description
    "This module defines the Tail-f NCS NED base identities.";

  revision 2011-06-01 {
    description
      "Released as part of NCS-1.6.";
  }

  identity generic-ned-id {
  }
  identity cli-ned-id {
  }
}
