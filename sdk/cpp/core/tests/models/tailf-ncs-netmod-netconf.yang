module tailf-ncs-netmod-netconf {
  namespace urn:ietf:params:xml:ns:netmod:notification;
  prefix "nm";

  import ietf-yang-types {
    prefix yang;
  }
  import tailf-common {
    prefix tailf;
  }
  import tailf-ncs {
    prefix ncs;
  }

  organization "Tail-f Systems";

  description
    "This module is used to handle NETCONF notifications to and
     from NCS.";

  revision 2011-12-13 {
    description
      "Released as part of NCS-1.8.

       Do not report the 'netconf' container for non-NETCONF devices.";
  }

  revision 2011-03-01 {
    description
      "Initial revision.  This module was releases in 1.0, but
       without a revision statement.

       Released as part of NCS-1.5.";
  }


  // This is an NCS-internal container
  container netconf {
    tailf:info "NCS NETCONF notification streams";
    config false;
    tailf:callpoint ncagent {
        tailf:internal;
    }
    container streams {
      tailf:info "Show the NCS NETCONF notification streams";
      list stream {
        tailf:info "Show the NCS NETCONF notification streams";
        key name;
        leaf name {
          tailf:info "NETCONF notification stream name";
          type string;
        }
        leaf description {
          tailf:info "NETCONF notification stream description";
          type string;
          mandatory true;
        }
        leaf replaySupport {
          tailf:info "If the stream supports replay";
          type boolean;
          mandatory true;
        }
        leaf replayLogCreationTime {
          tailf:info "The earliest available logged notification";
          type yang:date-and-time;
          mandatory true;
        }
        leaf replayLogAgedTime {
          tailf:info "Timestamp of the last notification aged out of the log";
          type yang:date-and-time;
        }
      }
    }
  }

  augment /ncs:devices/ncs:device/ncs:live-status {
    // only augment netconf devices
    when "../ncs:device-type/ncs:netconf";
    container netconf {
      tailf:info "Show the device NETCONF notification streams";
      config false;
      presence "the device has support for NETCONF notifications";
      tailf:display-when "../ncs:device-type/ncs:netconf";
      tailf:callpoint ncs_live {
        tailf:internal;
      }
      container streams {
      tailf:info "Show the device NETCONF notification streams";
        list stream {
          key name;
          leaf name {
            tailf:info "NETCONF notification stream name";
            type string;
          }
          leaf description {
            tailf:info "NETCONF notification stream description";
            type string;
            mandatory true;
          }
          leaf replaySupport {
            tailf:info "If the stream supports replay";
            type boolean;
            mandatory true;
          }
          leaf replayLogCreationTime {
            tailf:info "The earliest available logged notification";
            type yang:date-and-time;
            mandatory true;
          }
          leaf replayLogAgedTime {
            tailf:info "Timestamp of the last notification aged out of the log";
            type yang:date-and-time;
          }
        }
      }
    }
  }
}
