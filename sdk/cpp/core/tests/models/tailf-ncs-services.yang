submodule tailf-ncs-services {

  belongs-to tailf-ncs {
    prefix ncs;
  }

  import tailf-common {
    prefix tailf;
  }

  import ietf-yang-types {
    prefix yang;
  }
  include tailf-ncs-common;
  include tailf-ncs-customers;
  include tailf-ncs-devices;

  organization "Tail-f Systems";

  description
    "This submodule contains a collection of YANG definitions for
     configuring and monitoring services in NCS.";

  revision 2015-03-19 {
    description
      "Released as part of NCS-3.4.

       Minor description enhancements.";
  }

  revision 2014-12-10 {
    description
      "Released as part of NCS-3.3.1.

       Changed the service's commit-queue status 'failed-admin-cleared'
       to 'admin-cleared' and added new state 'commit-queue-failed'.";
  }

  revision 2014-11-19 {
    description
      "Released as part of NCS-3.3.

       Changed data type of 'commit-queue/queue-item' from int64
       to uint64.";
  }

  revision 2014-06-30 {
    description
      "Released as part of NCS-3.2.

       Use ncs-commit-* groupings in re-deploy and un-deploy.

       Changed a service's commit-queue/status enumeration to match
         the enumeration in /devices/device/commit-queue/status.

       Changed a service's commit-queue/failed-devices from a leaf-list
         to a list, and added some info.";
  }

  revision 2014-05-20 {
    description
      "Released as part of NCS-3.1.1.1.

       Added no-overwrite to un-deploy and re-deploy.

       Changed the names of the status leaf in the commit-queue stats
         container, in order to align with the status in
         /devices/commit-queues/queue-item/status.";
  }

  revision 2014-05-08 {
    description
      "Released as part of NCS-3.1.1.

       Added addtional fields in the commit-queue stats container with
       information about the error returned by the device, including
       the entire configuration data which was rejected";
  }

  revision 2014-04-02 {
    description
      "Released as part of NCS-3.1.";
  }

  revision 2013-11-12 {
    description
      "Released as part of NCS-3.0.

       Removed use of grouping service-data-no-hook in list /services/service.

       Removed callpoint ncs-rfs-service-case-hook in list /services/service.

       Removed action self-test in list /services/service.

       Removed leaf action-opaque from grouping service-data-no-hook/private.

       Removed leaf data-opaque from grouping service-data-no-hook/private.

       Removed grouping service-data-no-hook and introduced parts in grouping
         service-data.

       Removed YANG extension service-template-name and grouping
         service-template-data.

       Renamed the output container 'xml' in 'check-sync' and 're-deploy'
         to 'result-xml'.  The name 'xml' is illegal in YANG.  Also, changed
         the resulting leaf 'data' to anyxml 'data'.

       Added an action 'get-modifications' that returns the modifications
         a service introduced, in CLI and XML format.

       Added leaf /services/global-settings/collect-forward-diff.";
  }

  revision 2013-06-18 {
    description
      "Released as part of NCS-2.3.

       Added YANG extensions servicepoint and grouping service-data, to be
         used by service data models.

       Removed fastmap and extended support for customer facing services.

       Deprecated the action /services/commit-dry-run.  Use
         commit dry-run in the CLI instead.

       Removed the actions /services/fastmap/disable and enable.  Use
         commit no-fastmap in the CLI instead.

       Removed /services/status-summary operational data container.

       Removed /services/service/uses-service.

       Removed /services/services/used-by-cust-service operational data
       Removed /services/services/service-status operational data
       Since these only could hold information for a subset of services.";
  }

  revision 2013-03-12 {
    description
      "Released as part of NCS-2.2.

       Added native format to /services/commit-dry-run.
       Added YANG extension service-template-name and grouping
         service-template-data.";
  }

  revision 2012-08-30 {
    description
      "Released as part of NCS-2.0.";
  }

  /*
   * Services implemented as callbacks.
   */

  extension servicepoint {
    argument id {
      tailf:arg-type {
        type tailf:identifier;
      }
    }
    tailf:use-in "list";
    tailf:use-in "container";
    tailf:substatement "description";
    tailf:substatement "tailf:opaque";
    tailf:substatement "tailf:internal";
    description
      "This statement marks the list or container in which it appears
       to be used as service parameters for a service implemented
       by a callback in a data provider.";
  }

  grouping service-data {
    description
      "Use this grouping together with ncs:servicepoint
       in order to get the common definitions for a service
       implemented by a callback function.";

    tailf:callpoint ncs-rfs-service-hook {
      tailf:transaction-hook subtree {
        tailf:invocation-mode per-transaction;
      }
    }

    uses service-check-sync;
    uses service-deep-check-sync;
    uses service-re-deploy;
    uses service-impacted-devices;
    uses service-customer-service;

    container commit-queue {
      config false;
      tailf:cdb-oper {
        tailf:persistent true;
      }

      description
        "When a service is committed through the commit-queue, these
         fields act as references regarding the state of this service
         instance.  In the worst case scenario, a service instance is
         in the 'failed' state.  This means that parts of the queued
         commit failed.

         If a service gets committed through the commit queue and the
         commit fails, the backpointers in the service data are
         followed and the affected service instances are updated and
         set to the 'failed' state.

         Depending on the nature of the failure, different techniques
         to reconciliate the service can be used.

         - If all configuration attempts towards a device has failed,
           it's possible to do a sync-from on the device(s) and then
           re-deploy all affected services.

         - If just a few configuration attempts have failed, the best
           technique is to fix the error, and then do a sync-to on
           all devices for the service. (each service has a leaf-list of
           which devices are touched by the service.

         - Yet another technique is to use un-deploy on the service once
           the error is fixed, and then follow up with a re-deploy.

         In the 'failed' state, these fields are reset if a new commit-queue
         transaction is affecting this service, or the service is re-deployed,
         or these fields are deleted using the specific purge action.
         In other cases the 'failed' state will remain.";

      leaf status {
        tailf:callpoint ncs {
          tailf:internal;
        }
        type enumeration {
          enum waiting {
            description
              "This service was committed through the commit queue
               and the data is in the queue, waiting to run.";
          }
          enum executing {
            description
              "The data for this service is currently executing at the
               head of the commit queue.";
          }
          enum blocking {
            description
              "One or more of the devices for the transaction
               of which this service instance is a part, exposes a
               transient error.  The queue item in the commit queue
               remains there until the device becomes operational
               or the queue is pruned.

               Examples of transient errors are connection failures
               and that if thre changes are rejected due to the device
               being locked.

               The status for the queue item, in
               /devices/commit-queue/queue-item, contains details
               about this state.";
          }
          enum blocked {
            description
              "The data for this service is waiting in the queue, and some
               other queue item ahead of this item is in state 'blocking'.";
          }
          enum failed {
            description
              "The data for the transaction was not successfully
               deployed on all devices.  This service is is not
               operational.

               Details about the error can be found in the
               'failed-device' list.

               The queue item itself is removed from the
               /devices/commit-queue/queue-item list when it fails.";
            tailf:code-name "service_failed";
          }
          enum admin-cleared {
            description
              "The queue item affecting this service has been administratively
               cleared. Either directly by a clear action on this service
               commit queue data, or indirectly because of a delete/prune
               action directly on the commit-queue queue-item.

               In either case, device data for this service may or may not
               have been deployed in the network.";
          }
          enum commit-queue-failed {
            description
              "The data for the transaction was not successfully
               deployed on all devices. Since serveral services where modified
               by this transaction, whether this service is operational or
               not is indecisive.

               Details about the error can be found in the
               'failed-device' list.

               The queue item itself is removed from the
               /devices/commit-queue/queue-item list when it fails.";
          }
        }
      }

      leaf cleared-by-admin {
        type empty;
        tailf:hidden full;
      }

      leaf no-of-impacted-services {
        tailf:hidden full;
        type uint32;
      }

      list failed-device {
        description
          "If the 'status' leaf is 'failed', this list contains detailed
           information on the devices that were responsible for the
           error of the commit queue item.";
        key name;
        leaf name {
          type leafref {
            path '/ncs:devices/ncs:device/ncs:name';
          }
        }
        leaf time {
          type yang:date-and-time;
          description
            "Time when the failure occured.";
        }
        leaf config-data {
          description
            "The configuration data that was rejected by the device,
             i.e., the data that was sent from NCS to the device.";
          tailf:cli-preformatted;
          type string;
        }
        leaf error {
          description
            "The error returned by the device.";
          type string;
        }
      }

      leaf queue-item {
        type uint64;
        description
          "If the queue item in the commit queue refers to this service
           this is the queue number.";
      }

      tailf:action clear {
        description
          "Administratively clear this item.
           Information about failed devices will remain for this service.";
        tailf:actionpoint ncsinternal {
        tailf:internal;
        }
      }

      tailf:action purge {
        description
          "Remove this item.
           If this action is invoked for an item which is in other states
           than 'failed' this data migth later reappear since this service
           is then still affected by an active commit-queue transaction";
        tailf:actionpoint ncsinternal {
        tailf:internal;
        }
      }

    }

    tailf:action un-deploy {
      description
        "Undo the effects on the network for this service instance
         but keep the service itself. The service can later be
         re-deployed. This is a means to deactivate a service, but
         keep it in the system.

         Another important usage of this action is the ability to
         introduce already existing services into an NCS node using
         the flag 'ignore-refcount', which deletes the network effects
         of a service instance ignoring the FastMap reference counter.
         See NCS User guide, section 'Reconciling existing services'.";

      tailf:info "Undo the effects of this service to the network";
      tailf:actionpoint ncsinternal {
        tailf:internal;
      }
      input {
        uses ncs-commit-params;
        leaf ignore-refcount {
          type empty;
          description
            "Unconditionally delete the device data created by the
             service, regardless of the refcount.";
        }
      }
      output {
        uses ncs-commit-result;
      }
    }

    container private {
      description
        "NCS service related internal data stored here.";
      tailf:hidden fastmap-private;
      leaf diff-set {
        description
          "Internal node use by NCS service manager to remember
           the reverse diff for a service instance. This is the
           data that is used by FastMap";
        tailf:hidden full;
        type binary;
      }
      leaf forward-diff-set {
        description
          "Internal node use by NCS service manager to remember
           the forwards diff for a service instance. This data is
           is used to produce the proper 'get-modifications' output";
        tailf:hidden full;
        type binary;
      }

      container property-list {
        description
          "Fastmap service instance data used by the service implementation.";
        list property {
          key name;
          leaf name {
            type string;
          }
          leaf value {
            type string;
          }
        }
      }
      leaf re-deploy-counter {
        tailf:hidden full;
        type int32;
        default 0;
      }
    }
  }

  /*
   * Common service groupings.
   */

  grouping service-check-sync {
    tailf:action check-sync {
      tailf:info "Check if device config is according to the service";
      description
        "Check if this service has been undermined, i.e., if this service
         was to be re-deployed, would it do anything. This action will
         invoke the FastMap code to create the change set that is compared
         to the existing data in CDB locally.

         If outformat is boolean, 'true' is returned if the service is
         in sync, i.e., a re-deploy would do nothing. If outformat is
         cli or xml, the changes that the service would do to the
         network if re-deployed are returned.";
      tailf:actionpoint ncsinternal {
        tailf:internal;
      }

      input {
        leaf outformat {
          type outformat4;
          default boolean;
        }
      }
      output {
        choice outformat {
          leaf 'in-sync' {
            type boolean;
          }
          container result-xml {
            list device {
              leaf name {
                type string;
              }
              anyxml data;
            }
          }
          container cli {
            list device {
              leaf name {
                type string;
              }
              leaf data {
                tailf:cli-preformatted;
                type string;
              }
            }
          }
          container native {
            list device {
              leaf name {
                type string;
              }
              leaf data {
                tailf:cli-preformatted;
                type string;
              }
            }
          }
        }
      }
    }
  }

  grouping service-deep-check-sync {
    tailf:action deep-check-sync {
      tailf:info "Check if device config is according to the service";
      description
        "Check if this service has been undermined on the device itself.
         The action 'check-sync' compares the output of the service
         code to what is stored in CDB locally. This action retrieves the
         configuration from the devices touched by the service and compares
         the forward diff set of the service to the retrieved data. This
         is thus a fairly heavy weight operation. As opposed to the check-sync
         action that invokes the FastMap code, this action re-applies the
         forward diff-set. This is the same output you see when inspecting
         the 'get-modifications' operational field in the service instance.

         If the device is in sync with CDB, the output of this action
         is identical to the output of the cheaper check-sync action";

      tailf:actionpoint ncsinternal {
        tailf:internal;
      }
      input {
        leaf outformat {
          type outformat-deep-check-sync;
          default boolean;
        }
      }
      output {
        choice outformat {
          leaf 'in-sync' {
            type boolean;
          }
          container result-xml {
            list device {
              leaf name {
                type string;
              }
              anyxml data;
            }
          }
          container cli {
            list device {
              leaf name {
                type string;
              }
              leaf data {
                tailf:cli-preformatted;
                type string;
              }
            }
          }
        }
      }
    }
  }

  grouping service-re-deploy {
    tailf:action re-deploy {
      tailf:info "Run/Dryrun the service logic again";
      description
        "Run the service code again, possibly writing the changes of
         the service to the network once again. If the dryrun option is used,
         the action simply reports (in different formats) what it would do";

      tailf:actionpoint ncsinternal {
        tailf:internal;
      }
      input {
        container dry-run {
          presence "";
          leaf outformat {
            type outformat3;
          }
        }
        uses ncs-commit-params;
      }
      output {
        choice outformat {
          container result-xml {
            list device {
              leaf name {
                type string;
              }
              anyxml data;
            }
          }
          container cli {
            list device {
              leaf name {
                type string;
              }
              leaf data {
                tailf:cli-preformatted;
                type string;
              }
            }
          }
          container native {
            list device {
              leaf name {
                type string;
              }
              leaf data {
                tailf:cli-preformatted;
                type string;
              }
            }
          }
        }
        uses ncs-commit-result;
      }
    }
  }

  grouping service-impacted-devices {

    leaf device-modifications {
      tailf:info "The device configurations this service created";
      type string;
      config false;
      status deprecated;
      tailf:cli-preformatted;
      description
        "Which device modifications have been performed by this
         service instance.

         This leaf is deprecated.  Use the action 'get-modifications'
         instead.";
      tailf:callpoint ncs {
        tailf:internal;
      }
    }

    tailf:action get-modifications {
      tailf:info "Get the configuration data this service created";
      description
        "Returns the configuration data this service created, either
         in CLI diff format, or XML edit-config format, if the diff is
         available.

         If the parameter 'reverse' is not given, the forward diff is
         returned.

         The parameter
         '/services/global-settings/collect-forward-diff' controls if
         the forward diff is stored or not.

         If the parameter 'reverse' is given, the FastMap diff is
         returned.  This is the diff that would be applied if the
         service was deleted.  This diff is always stored.";
      tailf:actionpoint ncsinternal {
        tailf:internal;
      }
      input {
        leaf outformat {
          type outformat2;
        }
        leaf reverse {
          type empty;
        }
      }
      output {
        choice outformat {
          leaf cli {
            type string;
            tailf:cli-preformatted;
          }
        }
        anyxml result-xml;
      }
    }

    leaf-list device-list {
      tailf:info "A list of devices this service instance has manipulated";
      type string;
      config false;
      description
        "A list of managed devices this service instance has manipulated.";
      tailf:callpoint ncs {
        tailf:internal;
      }
    }
  }

  grouping service-customer-service {
    leaf-list used-by-customer-service {
      tailf:info "Customer facing services using this service";
      type leafref {
        path "/ncs:services/ncs:customer-service/ncs:object-id";
      }
      config false;
      tailf:callpoint ncs {
        tailf:internal;
      }
    }
  }

  /*
   * Data tree.
   */

  container services {
    tailf:info "The services managed by NCS";

    description
      "The services managed by NCS.";


    container global-settings {

      leaf collect-forward-diff {
        tailf:info "Toggle the collection of service data";
        description
          "When creating a service instance we can choose to also
           collect the forward diff.  I.e., remember what the service
           did.  This drives the formatting of the runtime statistics
           'get-modifications' for a service.  We always collect the
           reverse for a service instance, that is the basis for the
           FastMap algoritm.  This consumes quite a bit of extra
           memory per service instance, so if we have huge amounts of
           services it may be worthwhile to turn this off.";
        type boolean;
        default false;
      }
    }

    tailf:action check-sync {
      tailf:info "Check if device configuration is according to the services";
      description
        "Check if any service has been undermined, i.e., if a service was
         to be re-deployed, would it do anything.";

      tailf:actionpoint ncsinternal {
        tailf:internal;
      }
      input {
        leaf supress-positive-result {
          type empty;
          tailf:info "Return list only contains negatives";
          description
            "Use this additional parameter to only return services that
             failed to sync.";
        }
      }
      output {
        list sync-result {
          leaf service-id {
            type string;
          }
          leaf in-sync {
            type boolean;
          }
        }
      }
    }

    tailf:action commit-dry-run {
      status deprecated;
      tailf:info "DEPRECATED - use commit dry-run instead";
      description
        "Commit without actually committing to see what modifications
         will be done towards the managed devices.  Thus if we want
         to know what effects on the network the made changes will
         have, this action can be used.

         This action is deprecated.  Use 'commit dry-run' instead.";
      tailf:cli-configure-mode;
      tailf:actionpoint ncsinternal {
        tailf:internal;
      }
      input {
        leaf outformat {
          type outformat3;
        }
      }
      output {
        list device {
          leaf name {
            type string;
          }
          leaf data {
            tailf:cli-preformatted;
            type string;
          }
        }
      }
    }

    container properties {
      tailf:info "Properties used when creating services";
      description
        "This is a placeholder for where additional service properties
         can be augmented.";
    }

    list customer-service {
      tailf:info "Service that can be linked to customer";

      key object-id;
      reference "TMForumPhaseVIII::SID Phase VIII::Service Domain::Service
                   ABE::Customer Facing Service";

      leaf object-id {
        tailf:info "Customer facing service";
        type string;
        reference "Service ABE::objectId";
      }
      leaf reference {
        type string;
        reference "Service ABE::description";
      }
      leaf customer {
        tailf:info "The customer";
        type leafref {
          path "/ncs:customers/ncs:customer/ncs:id";
        }
        description
          "Customer for this service.";
      }
      list service {
        tailf:info "List of resource facing services";
        key service-id;
        description
          "Resource facing services for this service.";

        leaf service-id {
          tailf:info "The resource facing service";
          type instance-identifier;
          description
            "Must refer to a resource facing service instance.";
        }
      }

      container properties {
        tailf:info "Augmented properties for customer services";
        description
          "This container can be used whenever you want to extend the
           customer service properties with additional proprietary
           information.";
      }
    }

    list service {
      tailf:info "List of resource facing services";
      key object-id;

      reference "TMForumPhaseVIII::SID Phase VIII::Service
                   Domain::Service ABE::Resource Facing Service";

      leaf object-id {
        tailf:info "Unique service id";
        tailf:cli-allow-range;
        type string;
        reference "Service ABE::objectId";
      }

      leaf reference {
        type string;
        reference "Service ABE::description";
      }

      container properties {
        tailf:info "Additional service properties";
        description
          "This container can be used whenever you want to extend the
           resource service properties with additional proprietary
           information.";
      }
      container type {
        tailf:info "The service types";
        choice service-type-choice {
          description
            "This choice is augmented by service instances such
             as MPLS VPN.";
        }
      }
    }
  }
}
