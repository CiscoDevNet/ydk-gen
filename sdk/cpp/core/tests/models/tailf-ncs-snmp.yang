module tailf-ncs-snmp {

  namespace "http://tail-f.com/ns/ncs-snmp";
  prefix ncs-snmp;

  import ietf-inet-types {
    prefix inet;
  }
  import tailf-common {
    prefix tailf;
  }
  import ietf-yang-types {
    prefix yang;
  }

  organization "Tail-f Systems";

  description
    "This module is private to NCS.";

  revision 2012-03-13 {
    description
      "Released as part of NCS-1.9.";
  }

  revision 2011-03-01 {
    description
      "Initial revision, released as part of NCS-1.5.";
  }

  container ncs-snmp {
    tailf:hidden full;
    presence "";
    description
      "This section defines settings which affect the behavior of the
       SNMP agent.";
    leaf enabled {
      type boolean;
      default false;
      description
        "enabled is either 'true' or 'false'. If 'true', the SNMP
         agent is enabled.";
    }
    leaf ip {
      type inet:ip-address;
      default 0.0.0.0;
      description
        "ip is an IP address which the ConfD SNMP agent should listen
         to. 0.0.0.0 means that it listens to the port
         for all IP addresses/interfaces
         on the machine.";
    }
    leaf port {
      type inet:port-number;
      default 161;
    }
    leaf-list extraIpPorts {
      type string;
      description
        "extraIpPorts is a space separated list of ip:port
         pairs which the SNMP agent also listens to.";
    }
    container mibs {
      presence "";
      description
        "A list of MIBs that should be loaded into the SNMP agent.";
      leaf-list file {
        type string;
        max-elements unbounded;
        description
          "file is the location of a MIB file that should be loaded
           into the SNMP agent. For example:
           <file>./TAIL-F-TEST-MIB.bin</file>.  The MIB
           file must be in binary format (.bin) produced with the
           confdc compiler.  For loading of a built-in MIB no path
           must be given.

           Example: <file>SNMP-USER-BASED-SM-MIB.bin</file>.";

      }
      leaf fromLoadPath {
        type boolean;
        default false;
        description
          "If true, any '.bin' file found in the load path is loaded at
           startup. Bult-in MIBs must still be listed explicitly using
           the 'file' leaf-list.";
      }
    }
    leaf temporaryStorageTime {
      type uint32;
      default 300;
      description
        "The time, in seconds, that the agent keeps temporary table
         entries before deleting them.  A table entry is temporary
         if its RowStatus column is 'notReady' or 'notInService'.";
    }
    container snmpVersions {
      presence "";
      description
        "The list of SNMP versions that the SNMP agent should
         understand.";
      leaf v1 {
        type boolean;
        default true;
        description
          "Setting the value to true will enable SNMP v1 in the SNMP
           agent.";
      }
      leaf v2c {
        type boolean;
        default true;
        description
          "Setting the value to true will enable SNMP v2c in the SNMP
           agent.";
      }
      leaf v3 {
        type boolean;
        default true;
        description
          "Setting the value to true will enable SNMP v3 in the SNMP
           agent.";
      }
    }
    container snmpEngine {
      presence "";
      description
        "Properties from the SNMP-FRAMEWORK-MIB (RFC3411) for the
         SNMP agent.";
      leaf snmpEngineID {
        type tailf:hex-list;
        mandatory true;
        description
          "The name of the SNMP engine. snmpEngineID is defined in
           the SNMP-FRAMEWORK-MIB (RFC3411).";
      }
      leaf snmpEngineMaxMessageSize {
        type uint64 {
          range "0 .. max";
        }
        default 50000;
        description
          "The maximum size of SNMP messages that the agent can send
           or receive.  The snmpEngineMaxMessageSize is defined in
           the SNMP-FRAMEWORK-MIB (RFC3411).";
      }
    }
    leaf authenticationFailureNotifyName {
      type string;
      default "";
      description "
            When the SNMP agent sends the standard
            authenticationFailure notification, it is delivered to the
            management targets defined for the snmpNotifyName in the
            snmpNotifyTable in SNMP-NOTIFICATION-MIB (RFC3413).  If
            authenticationFailureNotifyName is the empty string
            (default), the notification is delivered to all management
            targets.
          ";
    }
    container system {
      presence "";
      description
        "The properties from the SNMPv2-MIB (RFC3418) for the SNMP agent.";
      leaf sysDescr {
        type string;
        description
          "A textual description of the entity.  This value should
           include the full name and version identification of the
           system's hardware type, software operating-system, and
           networking software.  The sysDescr is defined in the
           SNMPv2-MIB (RFC3418).";
      }
      leaf sysObjectID {
        type yang:object-identifier;
        description
          "The vendor's authoritative identification of the network
           management subsystem contained in the entity.  The
           sysObjectID is defined in the SNMPv2-MIB (RFC3418).";
      }
      leaf sysServices {
        type uint64 {
          range "0 .. max";
        }
        default 72;
        description
          "A value which indicates the set of services that this
           entity may potentially offer.  The sysServices is defined
           in the SNMPv2-MIB (RFC3418).";
      }
      container sysORTable {
        presence "";
        description
          "Entries that will populate the sysORTable from SNMPv2-MIB.";
        list sysOREntry {
          key sysORIndex;
          leaf sysORIndex {
            type uint64 {
              range "0 .. max";
            }
            description
              "The index for this row in the table.";
          }
          leaf sysORID {
            type yang:object-identifier;
            mandatory true;
            description
              "The OID of the AGENT-CAPABILITIES invocation.";
          }
          leaf sysORDescr {
            type string;
            mandatory true;
            description
              "A textual description of capabilities defined in sysORID.";
          }
        }
      }
    }
    leaf is-initialized-cfg {
      type boolean;
      default false;
    }
  }
}
