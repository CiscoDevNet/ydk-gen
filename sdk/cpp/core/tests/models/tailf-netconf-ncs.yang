module tailf-netconf-ncs {
  namespace "http://tail-f.com/ns/netconf/ncs";
  prefix ncsnc;

  import ietf-netconf {
    prefix nc;
  }
  import tailf-netconf-transactions {
    prefix tr;
  }
  import tailf-ncs {
    prefix ncs;
  }
  import tailf-common {
    prefix tailf;
  }

  organization "Tail-f Systems";

  description
    "This module defines extensions to NETCONF for NCS.";

  revision 2014-11-19 {
    description
      "Released as part of NCS-3.3.

       The groupings ncs:ncs-commit-params and ncs:ncs-commit-result
       has changed.

       Changed data type of leaf commit-queue-id from int64 to uint64";
  }

  revision 2014-06-30 {
    description
      "Released as part of NCS-3.2.

       Added new commit parameter 'dryrun'.
       Renamed (broken) 'through-commit-queue' to 'async-commit-queue'.
       Added new commit parameter 'sync-commit-queue'.
       Added 'commit-queue' output parameter.";
  }

  revision 2014-05-20 {
    description
      "Released as part of NCS-3.1.1.1.

       Added no-overwrite to ncs-commit-params.";
  }

  revision 2013-06-18 {
    description
      "Initial revision, released as part of NCS-2.3.";
  }

  augment "/nc:commit/nc:input" {
    uses ncs:ncs-commit-params;
  }
  augment "/nc:commit/nc:output" {
    uses ncs:ncs-commit-result;
  }

  augment "/nc:edit-config/nc:input" {
    when "nc:target/nc:running";
    uses ncs:ncs-commit-params;
  }
  augment "/nc:edit-config/nc:output" {
    uses ncs:ncs-commit-result;
  }

  augment "/nc:copy-config/nc:input" {
    when "nc:target/nc:running";
    uses ncs:ncs-commit-params;
  }
  augment "/nc:copy-config/nc:output" {
    uses ncs:ncs-commit-result;
  }

  augment "/tr:prepare-transaction/tr:input" {
    uses ncs:ncs-commit-params;
    container dryrun {
      presence "";
      leaf outformat {
        type ncs:outformat3;
        default xml;
      }
    }
  }

  augment "/tr:commit-transaction/tr:output" {
    uses ncs:ncs-commit-result;
  }

  augment "/tr:prepare-transaction/tr:output" {
    container dryrun-result {
      list device {
        key "name";
        leaf name {
          type string;
        }
        leaf data {
          type string;
        }
      }
    }
  }

  tailf:error-info {
    leaf commit-queue-id {
      type uint64;
      description
        "Id uniquely identifying a commit queue item on node";
    }
  }

}
