module tailf-ncs-monitoring-ann {
  namespace "urn:dummy";
  prefix dummy;

  import tailf-common {
    prefix tailf;
  }
  import tailf-ncs-monitoring {
    prefix tfnm;
  }


  tailf:annotate "/tfnm:ncs-state" {
    tailf:callpoint "confd" {
      tailf:internal;
    }

    tailf:info "NCS status information";
  }
}
