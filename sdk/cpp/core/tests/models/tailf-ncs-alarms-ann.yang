module tailf-ncs-alarms-ann {
  namespace "urn:dummy";
  prefix dummy;

  import tailf-ncs-alarms {
    prefix al;
  }
  import tailf-ncs {
    prefix ncs;
  }
  import tailf-common {
    prefix tailf;
  }

  tailf:annotate "/al:alarms/al:summary" {
    tailf:callpoint ncs {
      tailf:internal;
    }
  }

  tailf:annotate "/ncs:devices/ncs:device/al:alarm-summary" {
    tailf:callpoint ncs {
      tailf:internal;
    }
  }

  tailf:annotate "/ncs:devices/ncs:device-group/al:alarm-summary" {
    tailf:callpoint ncs {
      tailf:internal;
    }
  }

  tailf:annotate "/al:alarms/al:alarm-list/al:number-of-alarms" {
    tailf:callpoint ncs {
      tailf:internal;
    }
  }


  tailf:annotate "/al:alarms/al:alarm-list" {
    tailf:cdb-oper {
      tailf:persistent true;
    }
  }


}
