submodule tailf-ncs-java-vm {

  belongs-to tailf-ncs {
    prefix ncs;
  }

  import ietf-inet-types {
    prefix inet;
  }
  import tailf-common {
    prefix tailf;
  }

  organization "Tail-f Systems";

  description
    "This submodule contains a collection of YANG definitions for
     configuring and monitoring the Java Virtual Machine in NCS.";

  revision 2013-04-24 {
    description
      "Released as part of NCS-2.2.1.

       Added /java-vm/exception-error-message.";
  }

  revision 2012-11-13 {
    description
      "Released as part of NCS-2.1.

       Removed /java-vm/java-thread-pool.";
  }

  revision 2012-08-30 {
    description
      "Released as part of NCS-2.0.";
  }

  typedef error-verbosity-type {
    type enumeration {
      enum standard {
        value 0;
        tailf:code-name "error_standard";
      }
      enum verbose {
        value 1;
        tailf:code-name "error_verbose";
      }
      enum trace {
        tailf:code-name "error_trace";
        value 2;
      }
    }
    description
      "Levels of verbosity for Exception error messages in DP";
  }

  typedef log-level-type {
    type enumeration {
      enum level-all {
        value 1;
      }
      enum level-debug {
        value 2;
      }
      enum level-error {
        value 3;
      }
      enum level-fatal {
        value 4;
      }
      enum level-info {
        value 5;
      }
      enum level-off {
        value 6;
      }
      enum level-trace {
        value 7;
      }
      enum level-warn {
        value 8;
      }
    }
    description
      "Levels of logging for Java packages in log4j.";
  }

  container java-vm {
    tailf:info "Control of the NCS Java VM";
    description
      "Configuration parameters to control how and if NCS shall start (and
       restart) the Java Virtual Machine, configuration parameters to
       control various properties of the Java application code, e.g.,
       logging, and statistics data about the Java application code.";
    leaf auto-start {
      tailf:info "NCS starts the Java VM";
      type boolean;
      default true;
      description
        "If 'true', NCS automatically starts the Java VM, using the
         'start-command'.";
    }
    leaf auto-restart {
      tailf:info "NCS restarts the Java VM";
      type boolean;
      default true;
      description
        "Restart the Java VM if it terminates.

         Only applicable if auto-start is 'true'.";
    }
    leaf start-command {
      tailf:info "Java VM start command";
      type string;
      description
        "The command which NCS will run to start the Java VM. If unset
         NCS will run the ncs-start-java-vm script in the NCS installation
         bin directory.

         Only applicable if auto-start is 'true'.";
    }
    container run-in-terminal {
      tailf:info "Run the VM inside a terminal such as xterm";
      description
        "Enable this feature to run the Java VM inside
         a terminal, such as xterm or gnome-terminal.

         This can be very convenient during development;
         to restart the Java VM, just kill the terminal.

         Only applicable if auto-start is 'true'.";
      leaf enabled {
        tailf:info "Enable terminal";
        type boolean;
        default false;
      }
      leaf terminal-command {
        tailf:info "The terminal command";
        type string;
        default
          "xterm -title ncs-java-vm -e";
      }
    }
    container stdout-capture {
      tailf:info "Capture stdout and stderr";
      description
        "Capture stdout and stderr from the Java VM.

         Only applicable if auto-start is 'true'.";
      leaf enabled {
        tailf:info "Enable stdout and stderr capture";
        type boolean;
        default true;
      }
      leaf file {
        tailf:info "Write Java VM output to file";
        type string;
        default "./ncs-java-vm.log";
        description
          "Write Java VM output to filename.";
      }
      leaf stdout {
        tailf:info "Write output to stdout";
        type empty;
        description
          "If present write output to stdout, useful together
           with the --foreground flag to ncs.";
      }
    }

    leaf connect-time {
      tailf:info "The time NCS waits for the Java VM to connect to NCS";
      type uint32;
      units "seconds";
      default 60;
      description
        "The time NCS waits for the Java VM to connect to NCS
         during a synchronous startup of NCS.

         If the timer expires the action defined in
         'synchronization-timeout-action' is taken.";
    }
    leaf initialization-time {
      tailf:info "Timeout for each NCS package component to initialize";
      type uint32;
      units "seconds";
      default 60;
      description
        "The time NCS waits for each NCS package component to
         initialize itself.

         If the timer expires the action defined in
         'synchronization-timeout-action' is taken.";
    }
    leaf synchronization-timeout-action {
      tailf:info "If the synchronous startup fails";
      type enumeration {
        enum log {
          tailf:info "Log this error condition and continue";
          description
            "Log this error condition and continue.";
        }
        enum log-stop {
          tailf:info "Log this error condition and try to stop the Java VM";
          description
            "Log this error condition and try to stop the Java VM.

             If auto-start is 'false', this action is identical to
             'log'.";
        }
        enum exit {
          tailf:info "Terminate NCS fatally";
          description
            "Terminate NCS fatally.";
        }
      }
      default log-stop;
      description
        "The action NCS takes if any of the timers 'connect-time' or
         'initialization-time' expires.";
    }
    container exception-error-message {
      tailf:info "Configure Java Exception error message verbosity";
      leaf verbosity {
        tailf:info "Verbosity level for exception error messages";
        type error-verbosity-type;
        description
          "Verbosity level value for error messages in the Java VM.";
      }
    }
    container java-logging {
      tailf:info "Configure Java Logging";
      list logger {
        tailf:info "List of loggers";
        key "logger-name";
        description
          "Each entry in this list holds one representation of a logger with
           a specific level defined by log-level-type. The logger-name
           is the name of a Java package.  logger-name can thus be for
           example com.tailf.maapi, or com.tailf etc.";

        leaf logger-name {
          tailf:info "The name of the Java package";
          type string;
          mandatory true;
          description
            "The name of the Java package for which this logger
             entry applies.";
        }
        leaf level {
          tailf:info "Log-level for this logger";
          type log-level-type;
          mandatory true;
          description
            "Corresponding log-level for a specific logger.";
        }
      }
    }
    leaf service-transaction-timeout {
      tailf:info "How long before a transaction on a service will timeout";
      type int32;
      units "seconds";
      default 120;
      description
        "How long before a transaction on a service will timeout.";
    }

    container jmx {
      tailf:info "Java Management Extensions settings";
      presence
        "Start a Java Management Extensions (JMX) Agent in the Java VM";
      leaf jndi-address {
        tailf:info "The hostname or ip for the RMI registry";
        type inet:ip-address;
        default "0.0.0.0";
        description
          "The hostname or ip for the RMI registry";
      }
      leaf jndi-port {
        tailf:info "The port for the RMI registry";
        type inet:port-number;
        default "4444";
        description
          "The port for the RMI registry";
      }
      leaf jmx-address {
        tailf:info "The hostname or ip for the JMX RMI server";
        type inet:ip-address;
        default "0.0.0.0";
        description
          "The hostname or ip for the JMX RMI server";
      }
      leaf jmx-port {
        tailf:info "The port for the JMX RMI server";
        type inet:port-number;
        default "4445";
        description
          "The port for the JMX RMI server";
      }
    }

    leaf start-status {
      tailf:info "";
      type enumeration {
        enum auto-start-not-enabled {
          description
            "Auto start is not enabled.";
        }
        enum stopped {
          description
            "The Java VM has been stopped or is not yet started.";
        }
        enum started {
          description
            "The Java VM has been started.  See the leaf 'status' to check
             the status of the Java application code.";
          tailf:code-name jvm_started;
        }
        enum failed {
          description
            "The Java VM has terminated.  If 'auto-restart'
             is enabled, the Java VM restart has been
             disabled due to too many frequent restarts.";
        }
      }
      description
        "The status of the start of the Java VM.  If auto-start is 'false',
         this leaf is 'auto-start-not-enabled'.";
      config false;
      tailf:callpoint ncs {
        tailf:internal;
      }
    }
    leaf status {
      tailf:info "Java application status";
      type enumeration {
        enum not-connected {
          description
            "The Java application code is not connected to NCS.";
        }
        enum initializing {
          description
            "The Java application code is connected to NCS, but not
             yet initialized.";
          tailf:code-name jvm_initializing;
        }
        enum running {
          description
            "The Java application code is connected and initialized.";
          tailf:code-name jvm_running;
        }
        enum timeout {
          description
            "The Java application connected to NCS, but failed to initialize
             within the stipulated timeout 'initialization-time'.";
          tailf:code-name jvm_timeout;
        }
      }
      config false;
      description
        "This leaf describes the status of the Java application code
         in NCS.";
      tailf:callpoint ncs {
        tailf:internal;
      }
    }


    tailf:action stop {
      tailf:info "Stop the Java VM";
      description
        "Stop the NCS Java VM.

         Only applicable if auto-start is 'true'.";
      tailf:actionpoint ncsinternal {
        tailf:internal;
      }
      output {
        leaf result {
          type string;
        }
      }
    }
    tailf:action start {
      tailf:info "Stop the Java VM";
      description
        "Start the Java VM.

         Only applicable if auto-start is 'true'.";
      tailf:actionpoint ncsinternal {
        tailf:internal;
      }
      output {
        leaf result {
          type string;
        }
      }
    }
    tailf:action restart {
      tailf:info "Restart the Java VM";
      description
        "Restart the Java VM.

         Only applicable if auto-start is 'true'.";
      tailf:actionpoint ncsinternal {
        tailf:internal;
      }
      output {
        leaf result {
          type string;
        }
      }
    }
  }
}
