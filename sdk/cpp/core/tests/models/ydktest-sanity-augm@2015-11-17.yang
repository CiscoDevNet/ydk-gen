module ydktest-sanity-augm {

  /*** NAMESPACE / PREFIX DEFINITION ***/

  namespace "http://cisco.com/ns/yang/ydktest-sanity-augm";


  prefix "ysanity-augm";

  /*** LINKAGE (IMPORTS / INCLUDES) ***/

  //import ietf-inet-types { prefix "inet"; }

  //import Cisco-IOS-XR-types { prefix "xr"; }

  import ydktest-sanity { prefix "ysanity"; }

  import ydktest-types { prefix "yt"; }


  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for sanity package.

     This module contains LIST definitions
     for the following management objects:


     Copyright (c) 2013-2014 by Cisco Systems, Inc.
     All rights reserved.";

  revision "2015-11-17" {
    description
      "Initial revision.";
  }

  grouping one-aug-level {
    description "testing for couple of leaves";
    container one-aug {
      description "config for one_level data";
      leaf number {
        description "integer value type";
        type int32;
      }

      leaf name {
        description "this is string value";
        type string;
      }
    }
  }


  grouping one-aug-level-w-list {
    container one-aug-list {
      description "config for one_level list data";
      list ldata {
        description "one list data";
        key "number";
        leaf number {
          description "integer value type";
          type int32;
        }

        leaf name {
          description "this is string value";
          type string;
        }
      }
    }
  }
  
  grouping leaf-aug {
    leaf augmented-leaf {
        type string;
    }
  }

  grouping one-twin-aug {
    description "augment runner with same name container but different namespace";
    container one {
      description "config for one_level data";
      leaf twin-number {
        description "integer value type";
        type int32;
      }
    }
  }

  /////////////////////////////////////////////////////////
  // native / interface / Tunnel
  /////////////////////////////////////////////////////////
  grouping config-interface-tunnel-grouping {
    container nhrp {
      description
        "NHRP Interface commands";
      container event-publisher {
        description
          "Enable NHRP smart spoke feature";
        leaf max-event-timeout {
          description
            "Number of seconds";
          type uint8 {
            range "1..22";
          }
        }
      }
      leaf group {
        description
          "group name string";
        type string;
      }
    }

    container tunnel {
      description
        "protocol-over-protocol tunneling";

      // interface * / tunnel bandwidth
      container bandwidth {
        description
          "Set tunnel bandwidth informational parameter";
        leaf receive {
          description
            "Receive bandwidth";
          type uint32;
        }
        leaf transmit {
          description
            "Transmit bandwidth";
          type uint32;
        }
      }

      // interface * / tunnel source
      leaf source {
        description
          "source of tunnel packets";
        type string;
      }

      // interface * / tunnel destination
      leaf destination {
        description
          "destination of tunnel";
        type string;
      }
    }
  }

  grouping tec {
    container testc {
      uses yt:tt;
    }
  }

  grouping config-router-ospf-grouping {
    list ospf {
      description
        "Open Shortest Path First (OSPF)";
      key "id";
      leaf id {
        type uint16 {
          range "1..65535";
        }
      }

      uses yt:passive-interface-grouping;

      list test {
        key "name";
        leaf name {
            type string;
        }
      }
    }
  }


  /////////////////////////////////////////////////////////
  // augmentation
  /////////////////////////////////////////////////////////
  augment "/ysanity:runner" {
    description "augment to one";
    uses one-twin-aug;
  }

  augment "/ysanity:runner/ysanity:one" {
    description "augment to one";
    uses one-aug-level;
  }
  
  augment "/ysanity:runner/ysanity:one" {
    description "augment leaf to one";
    uses leaf-aug;
  }

  augment "/ysanity:runner/ysanity:one-list" {
    description "augment to one";
    uses one-aug-level-w-list;
  }

  // 2 level augment
  augment "/ysanity:runner/ysanity:one-list/ysanity-augm:one-aug-list" {
    description "augment to one";
    leaf enabled {
      description "integer value type";
      type boolean;
    }
  }

  augment "/ysanity:native/ysanity:interface/ysanity:Tunnel" {
    uses config-interface-tunnel-grouping;
  }

  augment "/ysanity:runner/ysanity:passive" {
    uses tec;
  }

  augment "/ysanity:runner/ysanity:one" {
    uses config-router-ospf-grouping;
  }
}
