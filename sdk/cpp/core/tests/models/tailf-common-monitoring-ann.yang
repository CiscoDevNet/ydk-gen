module tailf-common-monitoring-ann {
  namespace "urn:dummy-common";
  prefix dummy;

  import tailf-common {
    prefix tailf;
  }

  tailf:annotate-module tailf-common-monitoring {
    tailf:annotate-statement grouping[name='common-monitoring-objects'] {
      tailf:annotate-statement container[name='internal'] {
        tailf:annotate-statement container[name='cdb'] {
          tailf:annotate-statement list[name='datastore'] {
            tailf:annotate-statement leaf[name='disk-size'] {
              tailf:cli-value-display-template "$(.|filesizeformat)";
            }
            tailf:annotate-statement leaf[name='ram-size'] {
              tailf:cli-value-display-template "$(.|filesizeformat)";
            }
          }
          tailf:annotate-statement list[name='client'] {
            tailf:annotate-statement leaf[name='type'] {
              tailf:annotate-statement type {
                tailf:annotate-statement enum[name='client'] {
                  tailf:code-name client_type;
                }
              }
            }
            tailf:annotate-statement leaf[name='lock'] {
              tailf:annotate-statement type {
                tailf:annotate-statement enum[name='subscription'] {
                  tailf:code-name sub_lock;
                }
              }
            }
          }
        }
      }
      tailf:annotate-statement container[name='loaded-data-models'] {
        tailf:annotate-statement list[name='data-model'] {
          tailf:annotate-statement choice[name='exported'] {
            tailf:annotate-statement leaf-list[name='exported-to'] {
              tailf:annotate-statement type[name='union'] {
                tailf:annotate-statement type[name='enumeration'] {
                  tailf:annotate-statement enum[name='netconf'] {
                    tailf:code-name "exp_netconf";
                  }
                  tailf:annotate-statement enum[name='cli'] {
                    tailf:code-name "exp_cli";
                  }
                  tailf:annotate-statement enum[name='webui'] {
                    tailf:code-name "exp_webui";
                  }
                  tailf:annotate-statement enum[name='rest'] {
                    tailf:code-name "exp_rest";
                  }
                  tailf:annotate-statement enum[name='snmp'] {
                    tailf:code-name "exp_snmp";
                  }
                }
              }
            }
          }
        }
      }
      tailf:annotate-statement container[name='netconf'] {
        tailf:annotate-statement container[name='listen'] {
          tailf:annotate-statement list[name='tcp'] {
            tailf:cli-table-legend "NETCONF TCP listen addresses:";
          }
          tailf:annotate-statement list[name='ssh'] {
            tailf:cli-table-legend "NETCONF SSH listen addresses:";
          }
        }
      }
      tailf:annotate-statement container[name='cli'] {
        tailf:annotate-statement container[name='listen'] {
          tailf:annotate-statement list[name='ssh'] {
            tailf:cli-table-legend "CLI SSH listen addresses:";
          }
        }
      }
      tailf:annotate-statement container[name='webui'] {
        tailf:annotate-statement container[name='listen'] {
          tailf:annotate-statement list[name='tcp'] {
            tailf:cli-table-legend "WebUI TCP listen addresses:";
          }
          tailf:annotate-statement list[name='ssl'] {
            tailf:cli-table-legend "WebUI SSL listen addresses:";
          }
        }
      }
      tailf:annotate-statement container[name='rest'] {
        tailf:annotate-statement container[name='listen'] {
          tailf:annotate-statement list[name='tcp'] {
            tailf:cli-table-legend "REST TCP listen addresses:";
          }
          tailf:annotate-statement list[name='ssl'] {
            tailf:cli-table-legend "REST SSL listen addresses:";
          }
        }
      }
      tailf:annotate-statement container[name='snmp'] {
        tailf:annotate-statement container[name='listen'] {
          tailf:annotate-statement list[name='udp'] {
            tailf:cli-table-legend "SNMP UDP listen addresses:";
          }
        }
      }
    }
  }

}
