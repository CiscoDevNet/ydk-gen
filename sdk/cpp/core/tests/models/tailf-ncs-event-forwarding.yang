module tailf-ncs-event-forwarding {
  namespace "http://tail-f.com/ns/ncs-event-forwarding";
  prefix ef;

  tailf:export none;

  import tailf-common {
    prefix tailf;
  }
  import ietf-yang-types {
    prefix yang;
  }

  organization "Tail-f Systems";

  description
    "This module defines a temporary solution to augmenting meta-data nodes
     needed by event forwarding.";

  revision 2015-03-19 {
    description
      "Released as part of NCS-3.4.";
  }

  tailf:structure metadata {
    leaf device-name {
      type string;
      description
        "The name of device emitting the notification.";
    }
    leaf stream-name {
      type string;
      description
        "The name of stream emitting the notification.";
    }
    leaf device-event-time {
      type yang:date-and-time;
      description
        "The event time from the originating device.";
    }
  }
}
