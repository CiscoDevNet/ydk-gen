submodule tailf-ncs-python-vm {

  belongs-to tailf-ncs {
    prefix ncs;
  }

  import ietf-inet-types {
    prefix inet;
  }
  import tailf-common {
    prefix tailf;
  }

  organization "Tail-f Systems";

  description
    "This submodule contains a collection of YANG definitions for
     configuring and monitoring the Python Virtual Machine in NCS.";

  revision 2015-06-16 {
    description
      "Initial version";
  }

  typedef py-log-level-type {
    type enumeration {
      enum level-debug {
        tailf:code-name py-level-debug;
        description
          "Detailed information, typically of interest only
           when diagnosing problems.";
      }
      enum level-info {
        tailf:code-name py-level-info;
        description
          "Confirmation that things are working as expected.";
      }
      enum level-warning {
        tailf:code-name py-level-warning;
        description
          "An indication that something unexpected happened,
           or indicative of some problem in the near future.
           The software is still working as expected.";
      }
      enum level-error {
        tailf:code-name py-level-error;
        description
          "Due to a more serious problem, the software has not
           been able to perform some function.";
      }
      enum level-critical {
        tailf:code-name py-level-critical;
        description
          "A serious error, indicating that the program itself
           may be unable to continue running.";
      }
      enum level-off {
        tailf:code-name py-level-off;
        description
          "Turn of logging completely.";
      }
    }
    description
      "Levels of logging for Python packages in 'logging'.";
  }

  container python-vm {
    tailf:info "Control of the NCS Python VM";
    description
      "Configuration parameters to control how and if NCS shall start (and
       restart) the Python Virtual Machine, configuration parameters to
       control various properties of the Python application code, e.g.,
       logging, and statistics data about the Python application code.";

    leaf auto-start {
      tailf:info "NCS starts the Python VM";
      type boolean;
      default true;
      description
        "If 'true', NCS automatically starts the Python VM, using the
         'start-command'.";
    }

    leaf auto-restart {
      tailf:info "NCS restarts the Python VM";
      type boolean;
      default true;
      description
        "Restart the Python VM if it terminates.

         Only applicable if auto-start is 'true'.";
    }

    leaf start-command {
      tailf:info "Python VM start command";
      type string;
      description
        "The command which NCS will run to start the Python VM. If unset
         NCS will run the ncs-start-python-vm script in the NCS installation
         bin directory.

         Only applicable if auto-start is 'true'.";
    }

    container run-in-terminal {
      tailf:info "Run the VM inside a terminal such as xterm";
      description
        "Enable this feature to run the Python VM inside
         a terminal, such as xterm or gnome-terminal.

         This can be very convenient during development;
         to restart the Python VM, just kill the terminal.

         Only applicable if auto-start is 'true'.";
      leaf enabled {
        tailf:info "Enable terminal";
        type boolean;
        default false;
      }
      leaf terminal-command {
        tailf:info "The terminal command";
        type string;
        default
          "xterm -title ncs-python-vm -e";
      }
    }

    container logging {
      tailf:info "Configure Python Logging";

      leaf log-file-prefix {
        tailf:info "Write Python VM output to file";
        type string;
        default "ncs-python-vm";
        description
          "Write Python VM output to filename constructed as
           <file-prefix>-<id>.log where id will be dynamically
           allocated at startup of the Python VMs.

           Note: Spurious output from a Python VM that NCS may
           gather will end up in a log common for all running
           Python VMs. Its name will be <file-prefix>.log";
      }

      leaf level {
        tailf:info "Log-level for this logger";
        type py-log-level-type;
        default level-warning;
        description
          "Corresponding log-level for a specific logger.";
      }
    }

    container status {
      tailf:info "Status information from the started Python VMs";
      description
        "Status information from the started Python VMs";
      list start {
        key node-id;
        tailf:info "Outcome from starting the Python threads/components";
        description
          "The status of all started Python VMs.";
        config false;
        tailf:callpoint ncs {
          tailf:internal;
        }
        leaf node-id {
          type string;
          description
            "A symbolic id for a started Python VM.
             The name is either the package-name of a single
             package, which code runs in this Python VM. Or the
             'python-package/vm-name' in which case the Python VM
             may be running code from several packages.";
        }
        list packages {
          key package-name;
          description
            "A list of packages";
          leaf package-name {
            type string;
            description
              "The package name";
          }
          list components {
            key component-name;
            description
              "The components";
            leaf component-name {
              type string;
              description
                "The component name";
            }
            leaf class-name {
              type string;
              description
                "The Python class name";
            }
            leaf status {
              type enumeration {
                enum started {
                  tailf:code-name py-class-started;
                  description
                    "The Python class was started without errors";
                }
                enum failed {
                  tailf:code-name py-class-failed;
                  description
                    "The Python class failed to start";
                }
              }
            }
            leaf error-info {
              type string;
              description
                "Error information from a failed Python class";
            }
          }
        }
      }

      list current {
        key node-id;
        tailf:info "Current status of the Python threads/components";
        description
          "The status of all started Python VMs.";
        config false;
        tailf:callpoint ncs {
          tailf:internal;
        }

        leaf node-id {
          type string;
          description
            "A symbolic id for a started Python VM.
             The name is either the package-name of a single
             package, which code runs in this Python VM. Or the
             'python-package/vm-name' in which case the Python VM
             may be running code from several packages.";
        }

        list packages {
          key package-name;
          description
            "A list of packages";

          leaf package-name {
            type string;
            description
              "The package name";
          }

          list components {
            key component-name;
            description
              "The components";

            leaf component-name {
              type string;
              description
                "The component name";
            }

            list class-names {
              key class-name;

              leaf class-name {
                type string;
                description
                  "The Python class name";
              }

              leaf 'status' {
                type enumeration {
                  enum running {
                    tailf:code-name py-class-running;
                    description
                    "The Python class was started without errors";
                  }
                  enum finished {
                    tailf:code-name py-class-finished;
                    description
                    "The Python class failed to start";
                  }
                }
              }
            }
          }
        }
      }
    }

    tailf:action stop {
      tailf:info "Stop the Python VM";
      description
        "Stop the NCS Python VM.

         Only applicable if auto-start is 'true'.";
      tailf:actionpoint ncsinternal {
        tailf:internal;
      }
      input {
        leaf name {
          mandatory true;
          description
            "Name of the machine to be started. This Name can
             either be a package name or a 'python-vm/vm-name'
             that can be found in one or several packages.";
          type string;
        }
      }
      output {
        leaf result {
          type string;
        }
      }
    }

    tailf:action start {
      tailf:info "Start the Python VM";
      description
        "Start the Python VM.

         Only applicable if auto-start is 'true'.";
      tailf:actionpoint ncsinternal {
        tailf:internal;
      }
      input {
        leaf name {
          mandatory true;
          description
            "Name of the machine to be started. This Name can
             either be a package name or a 'python-vm/vm-name'
             that can be found in one or several packages.";
          type string;
        }
      }
      output {
        leaf result {
          type string;
        }
      }
    }
  }
}
