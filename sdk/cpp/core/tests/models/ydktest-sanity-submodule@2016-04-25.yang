submodule ydktest-sanity-submodule {
   belongs-to ydktest-sanity {
    prefix ydkut;
  }

  /*** NAMESPACE / PREFIX DEFINITION ***/

  /*** LINKAGE (IMPORTS / INCLUDES) ***/

  //import ietf-inet-types { prefix "inet"; }

  //import Cisco-IOS-XR-types { prefix "xr"; }


  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for sanity package.

     This module contains LIST definitions
     for the following management objects:
    

     Copyright (c) 2013-2014 by Cisco Systems, Inc.
     All rights reserved.";

  revision "2016-04-25" {
    description
      "Initial revision.";
  }

  grouping one-sub-level {
    description "testing for couple of leaves";
    container one-aug {
      description "config for one_level data";
      leaf number {
        description "integer value type";
        type int32;
      }

      leaf name {
        description "this is string value";
        type string;
      }
    }
  }
   
  container sub-test {
      uses one-sub-level;
  }
}
