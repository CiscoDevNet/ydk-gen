module bgp-operational {

  yang-version "1";

  // namespace
  // TODO: change to an ietf or other more generic namespace
  namespace "http://openconfig.net/yang/bgp-operational";

  prefix "bgp-op";

  // import some basic inet types
  import ietf-inet-types { prefix inet; }
  import ietf-yang-types { prefix yang; }
  import bgp-types { prefix bgp-types; }

  // Import for mapping annotation
  import oc-xr-mapping { prefix xr; }

  // meta

  organization
    "OpenConfig working group";

  contact
    "OpenConfig working group
    netopenconfig@googlegroups.com";

  description
    "This module is part of a YANG model for BGP protocol
    configuration, focusing on operational data (i.e., state
    variables) related to BGP operations";


  revision "2015-05-15" {
    description
      "Initial revision";
    reference "TBD";
  }

  xr:mapping {
    xr:model-id "oc";
    xr:module-id "bgp";
    xr:target {
      xr:model-id "xr";
      xr:default-prefix "cfg";
      xr:namespace "cfg|http://cisco.com/ns/yang/Cisco-IOS-XR-ipv4-bgp-cfg";
      xr:namespace "opr|http://cisco.com/ns/yang/Cisco-IOS-XR-ipv4-bgp-oper";
    }
  }

  // extension statements

  // feature statements

  // identity statements

  // typedef statements

  // grouping statements

  grouping bgp-counters-message-types_common {
    description
      "Grouping of BGP message types, included for re-use
      across counters";

    leaf UPDATE {
      type uint64;
      description
        "Number of BGP UPDATE messages announcing, withdrawing
        or modifying paths exchanged.";
      xr:map-to {
        xr:from {
          xr:parent "/bgp/neighbors/neighbor/state/messages/sent";
          xr:path 
            "opr:/bgp/instances/instance/instance-active/" +
            "default-vrf/neighbors/neighbor[neighbor-address]/" +
            "message-statistics/update/tx/count";
        }
        xr:from {
          xr:parent "/bgp/neighbors/neighbor/state/messages/received";
          xr:path 
            "opr:/bgp/instances/instance/instance-active/" +
            "default-vrf/neighbors/neighbor[neighbor-address]/" +
            "message-statistics/update/rx/count";
        }
      }
    }

    leaf NOTIFICATION {
      type uint64;
      description
        "Number of BGP NOTIFICATION messages indicating an
        error condition has occurred exchanged.";
      xr:map-to {
        xr:from {
          xr:parent "/bgp/neighbors/neighbor/state/messages/sent";
          xr:path 
            "opr:/bgp/instances/instance/instance-active/" +
            "default-vrf/neighbors/neighbor[neighbor-address]/" +
            "message-statistics/notification/tx/count";
        }
        xr:from {
          xr:parent "/bgp/neighbors/neighbor/state/messages/received";
          xr:path 
            "opr:/bgp/instances/instance/instance-active/" +
            "default-vrf/neighbors/neighbor[neighbor-address]/" +
            "message-statistics/notification/rx/count";
        }
      }
    }
  }


  grouping bgp-context-pfx-path-counters_common {
    description
      "Grouping containing common counters relating to prefixes and
      paths";

    leaf total-paths {
      type uint32;
      description
        "Total number of BGP paths within the context";
      xr:map-to {
        xr:from {
          xr:parent "/bgp/global/afi-safis/afi-safi/state";
          xr:description
            "Set 'default' for instance-name and '00' for process-id";
          xr:path
            "opr:/bgp/instances/instance/instance-active/default-vrf/afs/" +
            "af[af-name]/af-process-infos/af-process-info/global/paths-num";
        }
        xr:from {
          xr:parent "/bgp/global/state";
          xr:description
            "Need to calculate the value by suming up values of all AF of " +
            "opr:/bgp/instances/instance/instance-active/default-vrf/afs/" +
            "af[af-name]/af-process-infos/af-process-info/global/paths-num" +
            "Set 'default' for instance-name and '00' for process-id";
          xr:function "";
        }
      }
    }

    leaf total-prefixes {
      type uint32;
      description
        "";
      xr:map-to {
        xr:from {
          xr:parent "/bgp/global/afi-safis/afi-safi/state";
          xr:path
            "opr:/bgp/instances/instance/instance-active/default-vrf/afs/" +
            "af[af-name]/global-af-process-info/global/scan-prefixes";
        }
        xr:from {
          xr:parent "/bgp/global/state";
          xr:description
            "Need to calculate the value by suming up values of all AF of " +
            "opr:/bgp/instances/instance/instance-active/default-vrf/afs/" +
            "af[af-name]/global-af-process-info/global/paths-num";
          xr:function "";
        }
      }
    }
  }

  grouping bgp-global_state {
    description
      "Grouping containing operational parameters relating to the
      global BGP instance";
    uses bgp-context-pfx-path-counters_common;
  }

  grouping bgp-global-afi-safi_state {
    description
      "Grouping containing operational parameters relating to each
      AFI-SAFI within the BGP global instance";
    uses bgp-context-pfx-path-counters_common;
  }

  grouping bgp-peer-group_state {
    description
      "Grouping containing operational parameters relating to a BGP
      peer group";
    uses bgp-context-pfx-path-counters_common;
  }

  grouping bgp-neighbor_state {
    description
      "Grouping containing operational state variables relating to a
      BGP neighbor";

    leaf session-state {
      type enumeration {
          enum IDLE {
            description
              "neighbor is down, and in the Idle state of the
              FSM";
          }
          enum CONNECT {
            description
              "neighbor is down, and the session is waiting for
              the underlying transport session to be established";
          }
          enum ACTIVE {
            description
              "neighbor is down, and the local system is awaiting
              a conncetion from the remote peer";
          }
          enum OPENSENT {
            description
              "neighbor is in the process of being established.
              The local system has sent an OPEN message";
          }
          enum OPENCONFIRM {
            description
              "neighbor is in the process of being established.
              The local system is awaiting a NOTIFICATION or
              KEEPALIVE message";
          }
          enum ESTABLISHED {
            description
              "neighbor is up - the BGP session with the peer is
              established";
          }
        }
      description
        "Operational state of the BGP peer";
      xr:map-to {
        xr:description
          "Value mapping: \n" +
          "  IDLE -> bgp-st-idle \n" +
          "  CONNECT -> bgp-st-connect \n" +
          "  ACTIVE -> bgp-st-active \n" +
          "  OPENSENT -> bgp-st-open-sent \n" + 
          "  OPENCONFIRM -> bgp-st-open-conf-irm \n" +
          "  ESTABLISHED -> bgp-st-estab";
        xr:path
          "opr:/bgp/instances/instance/instance-active/default-vrf/" +
          "neighbors/neighbor[neighbor-address]/connection-state";
      }
    }

    leaf-list supported-capabilities {
    	type string;
    /*   type identityref {
        base bgp-types:bgp-capability;
      }*/
      description
        "BGP capabilities negotiated as supported with the peer";
      xr:map-to {
        xr:path
          "opr:/bgp/instances/instance/instance-active/" +
          "default-vrf/neighbors/neighbor[neighbor-address]/" +
          "is-route-refresh-capability-received";
        xr:path
          "opr:/bgp/instances/instance/instance-active/" +
          "default-vrf/neighbors/neighbor[neighbor-address]/" +
          "is-gr-aware";
        xr:path
          "opr:/bgp/instances/instance/instance-active/" +
          "default-vrf/neighbors/neighbor[neighbor-address]/" +
          "is4-byte-as-capability-received";
        xr:path
          "opr:/bgp/instances/instance/instance-active/" +
          "default-vrf/neighbors/neighbor[neighbor-address]/" +
          "is4-byte-as-capability-sent";
        xr:path
          "opr:/bgp/instances/instance/instance-active/" +
          "default-vrf/neighbors/neighbor[neighbor-address]/" +
          "multi-protocol-capability-received";
      }
    }
  }

  grouping bgp-neighbor-afi-safi_state {
    description
      "Operational state on a per-AFI-SAFI basis for a BGP
      neighbor";

    leaf active {
      type boolean;
      description
        "This value indicates whether a particular AFI-SAFI has
        been succesfully negotiated with the peer. An AFI-SAFI
        may be enabled in the current running configuration, but a
        session restart may be required in order to negotiate the new
        capability.";
      xr:map-to {
        xr:path
          "opr:/bgp/instances/instance/instance-active/" +
          "default-vrf/neighbors/neighbor[neighbor-address]/af-data/af-name";
        xr:path
          "opr:/bgp/instances/instance/instance-active/" +
          "default-vrf/neighbors/neighbor[neighbor-address]/af-data/" +
          "is-neighbor-af-capable";
      }
    }

    uses bgp-neighbor-prefix-counters_state;
  }

  grouping bgp-neighbor-prefix-counters_state {
    description
      "Counters for BGP neighbor sessions";

    container prefixes {
      description "Prefix counters for the BGP session";
      xr:map-to {
        xr:path
          "opr:/bgp/instances/instance/instance-active/" +
          "default-vrf/neighbors/neighbor[neighbor-address]/af-data";
      }
      leaf received {
        type uint32;
        description
          "The number of prefixes received from the neighbor";
        xr:map-to {
          xr:path "opr:af-name";
          xr:path "opr:prefixes-accepted";
        }
      }

      leaf sent {
        type uint32;
        description
          "The number of prefixes advertised to the neighbor";
        xr:map-to {
          xr:path "opr:af-name";
          xr:path "opr:prefixes-advertised";
        }
      }

      leaf installed {
        type uint32;
        description
          "The number of advertised prefixes installed in the
          Loc-RIB";
      }
    }
  }

  grouping bgp-neighbor-message-counters-sent_state {
    description
      "Counters relating to messages sent to a BGP neighbor";
    uses bgp-counters-message-types_common;
  }

  grouping bgp-neighbor-message-counters-received_state {
    description
      "Counters relating to the mesages received from a BGP
      neighbor";
    uses bgp-counters-message-types_common;
  }

  grouping bgp-neighbor-queue-counters_state {
    description
      "Counters relating to the message queues associated with the
      BGP peer";
    leaf input {
      type uint32;
      description
        "The number of messages received from the peer currently
        queued";
      xr:map-to {
        xr:from {
          xr:parent
            "/bgp/neighbors/neighbor/state/queues";
          xr:path 
            "opr:/bgp/instances/instance/instance-active/" +
            "default-vrf/neighbors/neighbor[neighbor-address]/" +
            "messages-queued-in";
        }
      }
    }

    leaf output {
      type uint32;
      description
        "The number of messages queued to be sent to the peer";
      xr:map-to {
        xr:from {
          xr:parent
            "/bgp/neighbors/neighbor/state/queues";
          xr:path 
            "opr:/bgp/instances/instance/instance-active/" +
            "default-vrf/neighbors/neighbor[neighbor-address]/" +
            "messages-queued-out";
        }
      }
    }
  }

  grouping bgp-neighbor-transport_state {
    description
      "Operational state parameters relating to the transport session
      used for the BGP session";

    leaf local-port {
      type inet:port-number;
      description
        "Local TCP port being used for the TCP session supporting
        the BGP session";
      xr:map-to {
        xr:path 
          "opr:/bgp/instances/instance/instance-active/" + 
          "default-vrf/neighbors/neighbor[neighbor-address]/" +
          "connection-local-port";
      }
    }

    leaf remote-address {
      type inet:ip-address;
      description
        "Remote address to which the BGP session has been
        established";
      xr:map-to {
        xr:path 
          "opr:/bgp/instances/instance/instance-active/" + 
          "default-vrf/neighbors/neighbor[neighbor-address]/" +
          "connection-remote-address";
      }
    }

    leaf remote-port {
      type inet:port-number;
      description
        "Remote port being used by the peer for the TCP session
        supporting the BGP session";
      xr:map-to {
        xr:path 
          "opr:/bgp/instances/instance/instance-active/" + 
          "default-vrf/neighbors/neighbor[neighbor-address]/" +
          "connection-remote-port";
      }
    }
  }

  grouping bgp-neighbor-error-handling_state {
    description
      "Operational state parameters relating to enhanced error
      error handling for BGP";

    leaf erroneous-update-messages {
      type uint32;
      description
        "The number of BGP UPDATE messages for which the
        treat-as-withdraw mechanism has been applied based
        on erroneous message contents";
    }
  }

  grouping bgp-neighbor-timers_state {
    description
      "Operational state parameters relating to BGP timers associated
      with the BGP session";

    leaf uptime {
      type yang:timeticks;
      description
        "This timer determines the amount of time since the
        BGP last transitioned in or out of the Established
        state";
    }

    leaf negotiated-hold-time {
      type decimal64 {
        fraction-digits 2;
      }
      description
        "The negotiated hold-time for the BGP session";
      xr:map-to {
        xr:path
          "opr:/bgp/instances/instance/instance-active/" +
          "default-vrf/neighbors/neighbor[neighbor-address]/hold-time";
      }
    }
  }

  grouping bgp-afi-safi_state {
    description
      "Operational state information relevant to all address
      families that may be carried by the BGP session";

    // placeholder - options in this container are
    // valid in both the global and per-neighbor
    // paths

  }

  grouping bgp-afi-safi-graceful-restart_state {
    description
      "Operational state information relevant to graceful restart
      for BGP";

    leaf peer-restart-time {
      type uint16 {
        range 0..4096;
      }
      description
        "The period of time (advertised by the peer) that
        the peer expects a restart of a BGP session to
        take";
      xr:map-to {
        xr:from {
          xr:parent "/bgp/neighbors/neighbor/graceful-restart/state";
          xr:path
            "opr:/bgp/instances/instance/instance-active/" +
            "default-vrf/neighbors/neighbor[neighbor-address]/" +
            "gr-restart-time";
        }
      }
    }

    leaf peer-restarting {
      type boolean;
      description
        "This flag indicates whether the remote neighbor is currently
        in the process of restarting, and hence received routes are
        currently stale";
    }

    leaf local-restarting {
      type boolean;
      description
        "This flag indicates whether the local neighbor is currently
        restarting. The flag is unset after all NLRI have been
        advertised to the peer, and the End-of-RIB (EOR) marker has
        been unset";
    }

    leaf mode {
      type enumeration {
        enum HELPER-ONLY {
          description
            "The local router is operating in helper-only mode, and
            hence will not retain forwarding state during a local
            session restart, but will do so during a restart of the
            remote peer";
        }
        enum BILATERAL {
          description
            "The local router is operating in both helper mode, and
            hence retains forwarding state during a remote restart,
            and also maintains forwarding state during local session
            restart";
        }
        enum REMOTE-HELPER {
          description
            "The local system is able to retain routes during restart
            but the remote system is only able to act as a helper";
        }
      }
      description
        "Ths leaf indicates the mode of operation of BGP graceful
        restart with the peer";
    }
  }

  grouping bgp-neighbor-afi-safi-graceful-restart_state {
    description
      "Operational state variables relating to the graceful-restart
      mechanism on a per-AFI-SAFI basis";

    leaf received {
      type boolean;
      description
        "This leaf indicates whether the neighbor advertised the
        ability to support graceful-restart for this AFI-SAFI";
    }

    leaf advertised {
      type boolean;
      description
        "This leaf indicates whether the ability to support
        graceful-restart has been advertised to the peer";
    }
  }


}
